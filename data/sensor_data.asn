SENSOR-DATA DEFINITIONS AUTOMATIC TAGS ::= BEGIN

SensorData ::= SEQUENCE {
    timestamp      INTEGER,          -- Unix timestamp
    accelerometer  SEQUENCE {
        x         REAL,              -- Accelerometer X-axis (in g)
        y         REAL,              -- Accelerometer Y-axis (in g)
        z         REAL               -- Accelerometer Z-axis (in g)
    },
    gyroscope      SEQUENCE {
        x         REAL,              -- Gyroscope X-axis (in °/s)
        y         REAL,              -- Gyroscope Y-axis (in °/s)
        z         REAL               -- Gyroscope Z-axis (in °/s)
    }
}

END
